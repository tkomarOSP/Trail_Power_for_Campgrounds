## R1: Requirements

## R2: Adaptability Requirements

## R3: Potential Extension

## R4: Potential Growth

## R5: Scalability

## R6: Cost and Schedule Constraints

## R7: Cost Constraints

## R8: Schedule Constraints

## R9: Design Constraints

## R10: Environmental Conditions

## R11: Functional Requirements

## R12: Interface Requirements

## R13: Energy

## R14: Human Interface

## R15: Information

## R16: Material Exchange

## R17: Physical Connections

## R18: Logistical Requirements

## R19: Handling

## R20: Packaging

## R21: Shipping

## R22: Sustainment Requirements

## R23: Level of Support

## R24: Provision of Facilities

## R25: Spare Parts

## R26: Support Personnel

## R27: Technical Documentation

## R28: Training

## R29: Transportation

## R30: Modes and/or States Requirements

## R31: Operational Requirements

## R32: Availability

## R33: Ergonomics

## R34: Human Factors

## R35: Maintainability

## R36: Reliability

## R37: Security

## R38: Performance Requirements

## R39: Physical Constraints

## R40: Dimensions

## R41: Volume

## R42: Weight

## R43: Policies and Regulations

## R44: Usability Requirements

## R45: Measurable Effectiveness

## R46: Measurable Efficiency

## R47: Measurable Satisfaction Criteria
